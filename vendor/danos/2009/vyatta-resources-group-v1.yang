module vyatta-resources-group-v1 {
	namespace "urn:vyatta.com:mgmt:vyatta-resources-group:1";
	prefix vyatta-resources-group-v1;

	include vyatta-resources-group-misc-v1;
	include vyatta-resources-dscp-group-v1;
	include vyatta-resources-protocol-group-v1;

	organization "AT&T Inc.";
	contact
		"AT&T
		 Postal: 208 S. Akard Street
		         Dallas, TX 75202, USA
		 Web: www.att.com";

	description
		"Copyright (c) 2017-2019, AT&T Intellectual Property.
		 All rights reserved.
		 Copyright (c) 2014-2017 by Brocade Communications Systems, Inc.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for Vyatta resource groups";

	revision 2019-12-09 {
		description "Moved protocol-group list out into submodule
			     to reinstate original orderering.";
	}
	revision 2019-11-29 {
		description "Moved resources group elements out into
			     two submodules for QoS VCI.";
	}
	revision 2019-06-26 {
		description "Update resource group commit handling
			     to improve performance even more.";
	}
	revision 2019-02-08 {
		description "Update resource group validation and commit
			     handling to improve performance.";
	}
	revision 2018-09-12 {
		description "Updated description and copyright.";
	}
	revision 2017-09-07 {
		description "Rename end-icmp-group to end-resource-group.
			     Replace end-port-group by end-resource-group.
			     Add support for DSCP and protocol resource
			     groups. Add support for address group range.";
	}
	revision 2017-06-23 {
		description "Let group addresses use mask 32 for IPv4 and
			     mask 128 for IPv6";
	}
	revision 2016-10-25 {
		description "Add warning validate script for address-groups named masquerade";
	}
	revision 2016-08-09 {
		description "Add descriptions to many nodes.
			     Move scripts from under tmplscripts.";
	}
	revision 2016-08-03 {
		description "Increase address-group max-elements from 32 to 1024";
	}
	revision 2016-03-28 {
		description "Remove use of bash in action scripts";
	}
	revision 2015-10-13 {
		description "Initial revision.";
	}
}
