module vyatta-ndpi-application-types-v1 {
	namespace "urn:vyatta.com:mgmt:vyatta-ndpi-application-types:1";
	prefix vyatta-ndpi-application-types-v1;

	organization "AT&T Inc.";
	contact	"AT&T
		 Postal: 208 S. Akard Street
		         Dallas, TX 75202, USA
		 Web: www.att.com";

	description
		"Copyright (c) 2020, AT&T Intellectual Property
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 Application types associated with the nDPI engine.

		 This file was auto-generated with
		 generation/application_types_yang.sh";

	revision 2020-01-06 {
		description "Initial revision based on nDPI 3.0.0.";
	}

	typedef application-types {
		/* New enums MUST only be added to the end of this list.
		 * Old enums MAY be deprecated or obsoleted, but must not be removed.
		 * It's not important to preserve alphabetical order.
		 */
		type enumeration {
			enum "chat";
			enum "cloud";
			enum "collaborative";
			enum "database";
			enum "datatransfer";
			enum "download";
			enum "email";
			enum "filesharing";
			enum "game";
			enum "media";
			enum "music";
			enum "network";
			enum "productivity";
			enum "remoteaccess";
			enum "rpc";
			enum "shopping";
			enum "socialnetwork";
			enum "softwareupdate";
			enum "streaming";
			enum "system";
			enum "video";
			enum "voip";
			enum "vpn";
			enum "web";
		}
	}
}
